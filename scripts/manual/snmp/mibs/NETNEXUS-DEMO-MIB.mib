NETNEXUS-DEMO-MIB DEFINITIONS ::= BEGIN

IMPORTS
    MODULE-IDENTITY, OBJECT-TYPE, Integer32, Gauge32, enterprises
        FROM SNMPv2-SMI
    DisplayString
        FROM SNMPv2-TC;

netNexusDemoMIB MODULE-IDENTITY
    LAST-UPDATED "202606110000Z"
    ORGANIZATION "NetNexus"
    CONTACT-INFO
        "NetNexus local SNMP MIB browser test module"
    DESCRIPTION
        "A small local MIB used to verify NetNexus MIB browser GET,
         GET-NEXT, SET and select-instance behavior."
    ::= { enterprises 55555 }

netNexusDemoObjects OBJECT IDENTIFIER ::= { netNexusDemoMIB 1 }
demoScalars        OBJECT IDENTIFIER ::= { netNexusDemoObjects 1 }
demoTables         OBJECT IDENTIFIER ::= { netNexusDemoObjects 2 }

demoAgentName OBJECT-TYPE
    SYNTAX      DisplayString
    MAX-ACCESS  read-only
    STATUS      current
    DESCRIPTION
        "Read-only scalar. Query as demoAgentName.0."
    ::= { demoScalars 1 }

demoAgentCounter OBJECT-TYPE
    SYNTAX      Integer32
    MAX-ACCESS  read-only
    STATUS      current
    DESCRIPTION
        "Read-only scalar whose value changes while the demo agent runs.
         Query as demoAgentCounter.0."
    ::= { demoScalars 2 }

demoWritableName OBJECT-TYPE
    SYNTAX      DisplayString
    MAX-ACCESS  read-write
    STATUS      current
    DESCRIPTION
        "Read-write scalar for verifying SET. Query or set as
         demoWritableName.0."
    ::= { demoScalars 3 }

demoIfTable OBJECT-TYPE
    SYNTAX      SEQUENCE OF DemoIfEntry
    MAX-ACCESS  not-accessible
    STATUS      current
    DESCRIPTION
        "A small interface table used to verify table instance selection."
    ::= { demoTables 1 }

demoIfEntry OBJECT-TYPE
    SYNTAX      DemoIfEntry
    MAX-ACCESS  not-accessible
    STATUS      current
    DESCRIPTION
        "One demo interface row. Instances are indexed by demoIfIndex."
    INDEX       { demoIfIndex }
    ::= { demoIfTable 1 }

DemoIfEntry ::= SEQUENCE {
    demoIfIndex   Integer32,
    demoIfName    DisplayString,
    demoIfStatus  Integer32,
    demoIfSpeed   Gauge32,
    demoIfAlias   DisplayString
}

demoIfIndex OBJECT-TYPE
    SYNTAX      Integer32
    MAX-ACCESS  read-only
    STATUS      current
    DESCRIPTION
        "The row index for demoIfTable."
    ::= { demoIfEntry 1 }

demoIfName OBJECT-TYPE
    SYNTAX      DisplayString
    MAX-ACCESS  read-only
    STATUS      current
    DESCRIPTION
        "Interface display name. Select-instance on this column should list
         .1, .2, .3, .10 and .20."
    ::= { demoIfEntry 2 }

demoIfStatus OBJECT-TYPE
    SYNTAX      INTEGER {
                    up(1),
                    down(2),
                    testing(3)
                }
    MAX-ACCESS  read-write
    STATUS      current
    DESCRIPTION
        "Writable demo interface status."
    ::= { demoIfEntry 3 }

demoIfSpeed OBJECT-TYPE
    SYNTAX      Gauge32
    MAX-ACCESS  read-only
    STATUS      current
    DESCRIPTION
        "Demo interface speed in bits per second."
    ::= { demoIfEntry 4 }

demoIfAlias OBJECT-TYPE
    SYNTAX      DisplayString
    MAX-ACCESS  read-write
    STATUS      current
    DESCRIPTION
        "Writable demo interface alias."
    ::= { demoIfEntry 5 }

END
